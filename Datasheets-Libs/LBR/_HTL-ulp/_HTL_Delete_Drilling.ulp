#usage "<b>Löscht die Bohrlegendenaus Layer 143 und 144. (Version 1.0) </b>\n"
       "<p>"
        "<p>"
       "<author>Autor: leopold.moosbrugger@htlr.snv.at</author><br>"
       "<br>"

#require 7.0300
       
real VERSION   = 1.0;

/*
 * CHANGELOG================================================
 *
 */

if (board)
{  
   board(B) 
   {
      string cmd = "";
      string sub_cmd;

      cmd += "Window FIT; ";
      cmd += "Display none 143 144; ";
      cmd += "GROUP ALL; ";
      cmd += "DELETE (> 0 0); ";
      cmd += "DISPLAY LAST; ";
      cmd += "MOVE ";
   
      // dlgMessageBox(cmd); 
      exit (cmd);
   }
} else 
{
   dlgMessageBox("_HTL_Delete_Drilling.ulp kann nur im Layout-Editor ausgeführt werden!", "&OK");
   exit ("MOVE");
}
