#usage "<b>Erstellt alle Ausdrucke. (Version 1.0) </b>\n"
       "<p>"
       "<p>"
       "<author>Autor: leopold.moosbrugger@htlr.snv.at</author><br>"
       "<br>"

#require 7.0300
       
real VERSION   = 1.0;

/*
 * CHANGELOG================================================
 *
 */

if (board)
{  
   board(B) 
   {
      string cmd = "";
      string sub_cmd;

      int Dr_b = 1;
      int Dr_t = 1;
      int Meas = 1;
      int LO_b = 1;
      int LO_t = 1;
      int LO_b_oP = 1;
      int LO_t_oP = 1;
      int Pl_b = 1;
      int Pl_t = 1;
      int Plw_t = 1;
      
      int Result = dlgDialog("Ausdrucke") {
         dlgGroup("Ausdrucke") {
         dlgCheckBox("Bohrplan (Bottom)", Dr_b);
         dlgCheckBox("Bohrplan (Top)", Dr_t);
         dlgCheckBox("Bemaßung", Meas);
         dlgCheckBox("Layout (Bottom)", LO_b);
         dlgCheckBox("Layout (Top)", LO_t);
         dlgCheckBox("Layout ohne Polygon (Bottom)", LO_b_oP);
         dlgCheckBox("Layout ohne Polygon (Top)", LO_t_oP);
         dlgCheckBox("Bestückungsplan (Bottom)", Pl_b);
         dlgCheckBox("Bestückungsplan (Top)", Pl_t);
         dlgCheckBox("Layout Work (Top)", Plw_t);
         }
         dlgPushButton("+Drucken") dlgAccept(1);
         dlgPushButton("+Abbrechen") dlgAccept(0);
      };

      if (Result)
      {
         if (Dr_b)
            cmd += "run _HTL_Print_Drilling_bot.ulp; ";

         if (Dr_t)
            cmd += "run _HTL_Print_Drilling_top.ulp; ";

         if (Meas)
            cmd += "run _HTL_Print_Measurement.ulp; ";

         if (Pl_b)
            cmd += "run _HTL_Print_Placement_bot.ulp; ";

         if (Pl_t)
            cmd += "run _HTL_Print_Placement_top.ulp; ";

         if (LO_b)
            cmd += "run _HTL_Print_Layout_bot.ulp; ";

         if (LO_t)
            cmd += "run _HTL_Print_Layout_top.ulp; ";

         if (LO_b_oP)
            cmd += "run _HTL_Print_Layout_bot_oP.ulp; ";

         if (LO_t_oP)
            cmd += "run _HTL_Print_Layout_top_oP.ulp; ";

         if (Plw_t)
            cmd += "run _HTL_Print_Layout_Work_top.ulp; ";
      }

      cmd += "ATTRIBUTE * BRD_SHEET_NAME 'Layout Work'; ";
      cmd += "WRITE; ";
      cmd += "Display none  1 16 17 18 19 20 21 22 23 24 25 26 27 28 41 42 51 52 101; ";
      cmd += "MOVE";
   
      // dlgMessageBox(cmd); 
      exit (cmd);
   }
} else 
{
   dlgMessageBox("_HTL_Polygon_OFF.ulp kann nur im Layout-Editor ausgefÃ¼hrt werden!", "&OK");
   exit ("MOVE");
}
