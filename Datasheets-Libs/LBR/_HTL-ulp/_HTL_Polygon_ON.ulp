#usage "<b>Schaltet Polygon_Ratsnest ein. (Version 1.0) </b>\n"
       "<p>"
       "<author>Autor: leopold.moosbrugger@htlr.snv.at</author><br>"
       "<br>"

#require 7.0300
       
real VERSION   = 1.0;

/*
 * CHANGELOG================================================
 *
 */

if (board)
{  
   board(B) 
   {
      string cmd = "";
      string sub_cmd;

      cmd += "SET POLYGON_RATSNEST ON; ";
      cmd += "RATSNEST; ";
      cmd += "MOVE";
   
      // dlgMessageBox(cmd); 
      exit (cmd);
   }
} else 
{
   dlgMessageBox("_HTL_Polygon_ON.ulp kann nur im Layout-Editor ausgeführt werden!", "&OK");
   exit ("MOVE");
}
