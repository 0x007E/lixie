#usage "Dieses ULP generiert eine Textdatei, mit dem Inhalt einer "
       "Bibliotheken fuer eine Datenbank"
       "<p>"
       "<author>Autor: leopold.moosbrugger@htlr.snv.at</author><br>"
       "<br>"

#require 7.0300


string version = "Version EAGLE-5.10.0";

if (EAGLE_VERSION * 100 + EAGLE_RELEASE < 410) 
{
   string h;
   sprintf(h, "Eagleversion %d %d ", EAGLE_VERSION, EAGLE_RELEASE);
   dlgMessageBox(h + "This ULP does not run in Eagle Versions older than 4.1", "OK");
   exit(0);
}

string fileName;

library(L) 
{
   fileName = strsub(L.name, 0, strstr(L.name, ".lbr")) + "_libs.txt";
   output(fileName, "wt") 
   {
      L.devicesets(DS) DS.devices(D) 
      {
         D.gates(G)
         {
            printf("%s   %s   %s   %s   %s   %s\n", filename(L.name), DS.name, D.name, D.package.name, G.name, G.symbol.name);
         }
      }
   }
}
